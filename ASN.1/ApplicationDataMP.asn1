--
-- 
-- Message format for Application Data of the OTA protocol data for EP11
--
-- * Copyright (c) 2012 SAIC. All Rights Reserved.
--
-- 2012-04-28 v1.0 First released version.
--
--

ApplicationDataMP

DEFINITIONS
AUTOMATIC TAGS ::= 
BEGIN



--
-- MP-UserLoggingInReq
--
MP-UserLoggingInReq ::= SEQUENCE
{
   password IA5String(SIZE(6..30)),
   deviceId IA5String(SIZE(1..80)) OPTIONAL
}

--
-- MP-UserLoggingInResp
--
MP-UserLoggingInResp ::= SEQUENCE
{
   token IA5String(SIZE(32))  OPTIONAL,

   tokenExpiration Timestamp  OPTIONAL,

   vinList SEQUENCE SIZE(1..256) OF Vin OPTIONAL
}

--
-- Vin
--
Vin ::= SEQUENCE
{

  vin IA5String(SIZE(17)),
  name OCTET STRING(SIZE(1..128)) OPTIONAL

}

--
--  CtlCommandReq
--
 CtlCommandReq ::= SEQUENCE
{
    pin IA5String(SIZE(32)),

    command  IA5String(SIZE(3)),

--wether TCU need return status
    needStatus BOOLEAN,

    config OCTET STRING(SIZE(0..63))
}

--
-- VehicleStatusResp
--
VehicleStatusResp ::= SEQUENCE
{

   vehicleStatus VehicleStatus

}

--
-- VehiclePathResp
--
VehiclePathResp ::= SEQUENCE
{
    leftRecordNumber INTEGER(0..255),

    pointList  SEQUENCE SIZE(1..256) OF Point OPTIONAL

}

--
-- Point
--
Point ::= SEQUENCE
{
    sequenceNumber INTEGER(0..4294967295),

    gpsPosition RvsPoint

}

--
-- AlarmSwitchReq
--
AlarmSwitchReq ::= SEQUENCE
{
    pin IA5String(SIZE(32)),

    alarmSwitchList SEQUENCE SIZE(1..16) OF AlarmSwitch

}

--
-- AlarmSwitch
--
AlarmSwitch ::= SEQUENCE
{
    alarmType AlarmSettingType,

    alarmSwitch BOOLEAN,

    functionSwitch BOOLEAN
}

--
-- MP-AlarmReq
--
MP-AlarmReq ::= SEQUENCE
{
    id INTEGER(0..281474976710655)

}

--
-- MP-AlarmResp
--
MP-AlarmResp ::= SEQUENCE
{
   alarmInfo AlarmInfo
}

--
-- AlarmSettingResp
--
AlarmSettingResp ::= SEQUENCE
{

    alarmSettingList SEQUENCE SIZE(1..16) OF AlarmSetting

}

--
-- AlarmSetting
--
AlarmSetting ::= SEQUENCE
{
    alarmType AlarmSettingType,

    alarmStatus BOOLEAN,

    functionStatus BOOLEAN
}

--
--  MessageListReq
--
MessageListReq ::= SEQUENCE
{
    startEndNumber StartEndNumber
}

--
--  MessageListResp
--
MessageListResp ::= SEQUENCE
{
    recordsNumber INTEGER(0..281474976710655),

    messages SEQUENCE SIZE(1..256) OF Message OPTIONAL

}

--
--  MessageDetailReq
--
MessageDetailReq ::= SEQUENCE
{
    messageId INTEGER(0..281474976710655)
}

--

--  MessageDetailResp
--
MessageDetailResp ::= SEQUENCE
{
   
    message Message

}

--
--  GetUnreadMessageCountResp
--
GetUnreadMessageCountResp ::= SEQUENCE
{
    totalNumber INTEGER(0..281474976710655)
}

--
--  MessageNoticeListReq
--
MessageNoticeListReq ::= SEQUENCE
{
    startEndNumber StartEndNumber
}

--
--  MessageNoticeListResp
--
MessageNoticeListResp ::= SEQUENCE
{
    messages SEQUENCE SIZE(1..256) OF Message OPTIONAL

}

--
--  Message
--
Message ::= SEQUENCE
{
   messageId INTEGER(0..281474976710655),

   messageType IA5String(SIZE(3)),

   title OCTET STRING(SIZE(1..128)),

   messageTime Timestamp,

   sender OCTET STRING(SIZE(1..64)),

   contentIdList SEQUENCE SIZE(1..256) OF ContentId OPTIONAL,

   content OCTET STRING(SIZE(1..2048)) OPTIONAL
}

--
--  ContentId
--
ContentId ::= SEQUENCE
{
    contentId  INTEGER(0..281474976710655)
}

--
--  FavoritePOIQueryReq
--
FavoritePOIQueryReq ::= SEQUENCE
{
    startEndNumber StartEndNumber
}


--
--  FavoritePOIQueryResp
--
FavoritePOIQueryResp ::= SEQUENCE
{
   totalNum INTEGER(0..281474976710655),

   poiList SEQUENCE SIZE(1..256) OF POI OPTIONAL
}


--
--  AddToFavoritePOIReq
--
AddToFavoritePOIReq ::= SEQUENCE
{
   poi POI
}

--
--  AddToFavoritePOIResp
--
AddToFavoritePOIResp ::= SEQUENCE
{
   poiId INTEGER(0..281474976710655)
}


--
--  DeleteFavoritePOIReq
--
DeleteFavoritePOIReq ::= SEQUENCE
{
    poiIdList SEQUENCE SIZE(1..65536) OF POIId
}

--
--  POIId
--
POIId ::= SEQUENCE
{
   poiId INTEGER(0..281474976710655)
}


--
--  POISendToCarReq
--
POISendToCarReq ::= SEQUENCE
{
   poiList SEQUENCE SIZE(1..256) OF POI
}

--
-- FuelEconomyRankingReq
--
FuelEconomyRankingReq ::= SEQUENCE
{
   rankingType RankingType,

   uid IA5String(SIZE(1..50)) OPTIONAL,

   startEndNumber StartEndNumber

}

--
-- FuelEconomyRankingResp
--
FuelEconomyRankingResp ::= SEQUENCE
{
   totalNumber INTEGER(0..281474976710655),

   userRankingInfo UserRankingInfo OPTIONAL,

   otherUsersRankingInfo SEQUENCE SIZE(1..256) OF UserRankingInfo OPTIONAL,

   averageFuelConsumption INTEGER(0..65535) OPTIONAL


}

--
-- SpeedReportReq
--
SpeedReportReq ::= SEQUENCE
{
   startEndNumber StartEndNumber,

   beginTime Timestamp,
   
   endTime Timestamp,

   unit Unit
}

--
-- SpeedReportResp
--
SpeedReportResp ::= SEQUENCE
{
   totalNumber INTEGER(0..281474976710655),

   averageSpeed INTEGER(0..65535),

   speedInfoList SEQUENCE SIZE(1..256) OF SpeedInfo OPTIONAL


}

--
-- SpeedInfo 
--
SpeedInfo ::= SEQUENCE
{
   speed INTEGER(0..65535),

   time  Timestamp,

   unit Unit
}


--
-- UserFuelEconomyRankingReq
--
UserFuelEconomyRankingReq ::= SEQUENCE
{
   rankingType RankingType,

   nikname OCTET STRING(SIZE(1..256)) OPTIONAL,

   startEndNumber StartEndNumber

}

--
-- UserFuelEconomyRankingResp
--
UserFuelEconomyRankingResp ::= SEQUENCE
{
   totalNumber INTEGER(0..281474976710655),

   userRankingInfo SEQUENCE SIZE(1..256) OF UserRankingInfo OPTIONAL


}


--
-- UserRankingInfo
--
UserRankingInfo ::= SEQUENCE
{
   ranking INTEGER(0..281474976710655),

   nikname OCTET STRING(SIZE(1..256)),

   model OCTET STRING(SIZE(1..256)) OPTIONAL,

   fuelConsumption INTEGER(0..65535),

   rankingChange INTEGER(0..281474976710655),

   rankingChangeType RankingChangeType

}

--
--  CityListDownloadReq
--
 CityListDownloadReq ::= SEQUENCE
{
    cityType CityType

}

--
--  CityListDownloadResp
--
 CityListDownloadResp ::= SEQUENCE
{
    cityList SEQUENCE SIZE(1..128) OF ProvinceInfo

}

--
-- ProvinceInfo
--
ProvinceInfo ::= SEQUENCE
{
   regionId IA5String(SIZE(6)),

   realName OCTET STRING(SIZE(1..64)),

   shortName IA5String(SIZE(1..16)),

   cityInfoList SEQUENCE SIZE(1..256) OF CityInfo
}

--
-- CityInfo
--
CityInfo ::= SEQUENCE
{
   regionId IA5String(SIZE(6)),

   realName OCTET STRING(SIZE(1..64)),

   shortName IA5String(SIZE(1..16))
}

--
--  RegionSettingReq
--
RegionSettingReq ::= SEQUENCE
{
   regionSettingSwitch RegionSettingSwitch,

   regionType RegionType OPTIONAL,

   nwPosition BasicPosition OPTIONAL,
  
   sePosition BasicPosition OPTIONAL,
   
   centerPosition BasicPosition OPTIONAL,
  
   radius INTEGER(0..281474976710655) OPTIONAL,

   regionId  IA5String(SIZE(6)) OPTIONAL

}

--
--  RegionSearchResp
--
RegionSearchResp ::= SEQUENCE
{
   regionSettingSwitch RegionSettingSwitch,

   regionType RegionType OPTIONAL,

   nwPosition BasicPosition OPTIONAL,
  
   sePosition BasicPosition OPTIONAL,
   
   centerPosition BasicPosition OPTIONAL,
  
   radius INTEGER(0..281474976710655) OPTIONAL,

   regionId  IA5String(SIZE(6)) OPTIONAL

}






--
-- POI
--
POI ::= SEQUENCE
{
   poiID INTEGER(0..281474976710655) OPTIONAL,

   isValid BOOLEAN OPTIONAL,

   basicPosition BasicPosition,

   cityCode IA5String(SIZE(6)),

   addressName OCTET STRING(SIZE(1..512)) OPTIONAL,

   phone IA5String(SIZE(1..50)) OPTIONAL,

   address OCTET STRING(SIZE(1..512)) OPTIONAL,

   postCode NumericString(SIZE(6)) OPTIONAL,

   creatTime Timestamp OPTIONAL

}


--
-- AlarmInfo
--
AlarmInfo ::= SEQUENCE
{
   alarmType AlarmType,

   abnormalAlarmType AbnormalAlarmType OPTIONAL,

   alarmTime Timestamp,

   vehicleStatus VehicleStatus

}

--
-- VehicleStatus
--
VehicleStatus ::= SEQUENCE
{

-- GPS Position
    gpsPosition RvsPoint,

    vehicleData OCTET STRING(SIZE(1..65536))

}

--
-- Query Start Number & End Number
--
StartEndNumber ::= SEQUENCE
{
   startNumber INTEGER(0..281474976710655),

   endNumber INTEGER(0..281474976710655)

}


--
-- RvsPoint
--
RvsPoint ::= SEQUENCE
{
   wayPoint	RvsWayPoint,

   timestamp	Timestamp,

   gpsStatus	GPSStatus

}

--
-- RvsWayPoint
--
RvsWayPoint ::= SEQUENCE
{
   position RvsWGS84Point,

   heading INTEGER(0..359),

   speed INTEGER(-1000..4500)


}

--
-- RvsWGS84Point
--
RvsWGS84Point ::= SEQUENCE
{
   --WGS84 decimal X 1000000 e.g. latitude 57.123456 => 57123456 
  latitude  INTEGER (-90000000..90000000),

  --WGS84 decimal X 1000000 e.g. longitude 10.123456 => 10123456
  longitude INTEGER (-180000000..180000000),

  --altitude,UNIT:meter
  altitude INTEGER (-100..8900)


}

--
-- Basic Position
--
BasicPosition ::= SEQUENCE
{
  
  --WGS84 decimal X 1000000 e.g. latitude 57.123456 => 57123456 
  latitude  INTEGER (-90000000..90000000),

  --WGS84 decimal X 1000000 e.g. longitude 10.123456 => 10123456
  longitude INTEGER (-180000000..180000000)
}




--
-- Timestamp
--
Timestamp ::= SEQUENCE
{
  
  -- seconds since 1970-01-01T00:00:00 UTC
  seconds INTEGER(0..4294967295)
}

--
-- GPS Status
--
GPSStatus ::= ENUMERATED
{
--NoGpsSignal = 0
  noGpsSignal(0),

--TimeFix = 1
  timeFix(1),

--Fix2D = 2
  fix2D(2),

--Fix3D = 3
  fix3D(3)

}

--
-- Alarm Setting Type
--
AlarmSettingType ::= ENUMERATED
{
--Abnormal Alarm = 0
  abnormal(0),

--Moving Alarm = 1
  moving(1),

--Region Alarm = 2
  region(2),

--Engin Start Alarm = 3
  enginStart(3),

--Engin Start Alarm = 4
  startVehicleStatus(4)

}

--
-- Alarm Type
--
AlarmType ::= ENUMERATED
{
--Abnormal Alarm = 0
  abnormal(0),

--Moving Alarm = 1
  moving(1),

--Region Alarm = 2
  region(2),

--Engin Start Alarm = 3
  enginStart(3)

}

--
-- Abnormal Alarm Type
--
AbnormalAlarmType ::= ENUMERATED
{
--CAN Alarm = 1
  can(1),

--G-sensor Alarm = 2
  gSensor(2),

--Tbox Alarm = 3
  tbox(3),

--Battery Alarm = 4
  battery(4)

}

--
-- Ranking Type
--
RankingType ::= ENUMERATED
{
--year ranking
  year(0),

--month ranking
  month(1),

--weekly ranking
  week(2)

}

--
-- Ranking Change Type
--
RankingChangeType ::= ENUMERATED
{
--no change
  noChange(0),

--up
  up(1),

--down
  down(2)

}



--
-- City Type
--
CityType ::= ENUMERATED
{
--interest city
  interest(0),

--all city
  all(1)

}


--
--Region Setting Switch
--
RegionSettingSwitch ::= ENUMERATED
{
--off
  off(0),

--out on
  outOn(1),

--inOn 
  inOn(2),

--On 
  on(3)
}

--
--Region Type
--
RegionType ::= ENUMERATED
{
--rectangle
  rectangle(0),

--circular
  circular(1),

--region 
  region(2)
}

--
-- Unit
--
Unit ::= ENUMERATED
{
--hour
  hour(0),

--day
  day(1),

--week
  week(2),


--month
  month(3)

}

END
