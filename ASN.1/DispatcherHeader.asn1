--
-- 
-- Message format for Dispatcher Body of the OTA protocol data
--
-- * Copyright (c) 2012 SAIC. All Rights Reserved.
--
-- 2012-04-28 v1.0 First released version.
--
--

DispatcherHeader

DEFINITIONS
AUTOMATIC TAGS ::= 
BEGIN

--
-- Dispatcher Header
--
DispatcherHeader ::= SEQUENCE
{
-- Protocal Version
    protocolVersion  INTEGER(0..255),

-- Security Context
    securityContext  INTEGER(0..65535),

-- Dispatcher Message Length    
    dispatcherMessageLength INTEGER(0..255),
    
-- Dispatcher Body Encoding 
    dispatcherBodyEncoding INTEGER(0..2)
}

END
